module virtualizer_mappings {
  namespace "urn:5gex:virtualizer_mappings";
  prefix "virtualizer_mappings";

  organization "5GEx";

  revision "2016-11-19" {
    description "Mapping resolution service for the virtualizer";
  }

  grouping object{
    leaf object {
      type leafref {
	path "";
      }
  }

  grouping mapping{
    uses object;
    container target {
      uses object;
      leaf domain {
      type string;
      }
    }
  }
  
  container mappings {
    list mapping{
      key "object";
      uses mapping;
    }
  }
}
